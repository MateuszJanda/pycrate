-- *asn1ate*:
-- https://github.com/kimgr/asn1ate
-- Hack: asn1ate not parse empty sequence ("SEQUENCE {}"), just replece by "SEQUENCE { asdf INTEGER }" to generate
-- pyasn1 code, and edit it.
--
-- *pyasn1*
-- https://github.com/etingof/pyasn1
-- $ python pyasn1gen.py asn1.1/PCCH-Message.asn1 > pyasn1_pcch_message.py
--
-- *libmich*
-- https://github.com/mitshell/libmich.git
--
-- Info:
-- http://www.etsi.org/deliver/etsi_ts/136300_136399/136331/08.06.00_60/ts_136331v080600p.pdf
-- https://www.itu.int/ITU-T/studygroups/com17/languages/X.680-0207.pdf
-- http://asn1-playground.oss.com/

PCCH-Message-Definition DEFINITIONS AUTOMATIC TAGS ::=
BEGIN

PCCH-Message ::= SEQUENCE {
    message PCCH-MessageType
}

PCCH-MessageType ::= CHOICE {
    c1 CHOICE {
        paging Paging
        },
    messageClassExtension SEQUENCE {}
}

Paging ::= SEQUENCE {
    pagingRecordList PagingRecordList OPTIONAL, -- Need ON
    systemInfoModification ENUMERATED {true} OPTIONAL, -- Need ON
    etws-Indication ENUMERATED {true} OPTIONAL, -- Need ON
    nonCriticalExtension Paging-v890-IEs OPTIONAL
}

Paging-v890-IEs ::= SEQUENCE {
    lateNonCriticalExtension OCTET STRING OPTIONAL,
    nonCriticalExtension Paging-v920-IEs OPTIONAL
}

Paging-v920-IEs ::= SEQUENCE {
    cmas-Indication-r9 ENUMERATED {true} OPTIONAL, -- Need ON
    nonCriticalExtension Paging-v1130-IEs OPTIONAL
}

Paging-v1130-IEs ::= SEQUENCE {
    eab-ParamModification-r11 ENUMERATED {true} OPTIONAL, -- Need ON
    nonCriticalExtension Paging-v13xx-IEs OPTIONAL
}

Paging-v13xx-IEs ::= SEQUENCE {
    redistributionIndication-r13 ENUMERATED {true} OPTIONAL, -- Need ON
    systemInfoModification-eDRX-r13 ENUMERATED {true} OPTIONAL, -- Need ON
    nonCriticalExtension SEQUENCE {} OPTIONAL
}

PagingRecordList ::= SEQUENCE (SIZE (1..maxPageRec)) OF PagingRecord

PagingRecord ::= SEQUENCE {
    ue-Identity PagingUE-Identity,
    cn-Domain ENUMERATED {ps, cs},
    ...
}

PagingUE-Identity ::= CHOICE {
    s-TMSI S-TMSI,
    imsi IMSI,
    ...
}

IMSI ::= SEQUENCE (SIZE (6..21)) OF IMSI-Digit

IMSI-Digit ::= INTEGER (0..9)

MMEC ::= BIT STRING (SIZE (8))

S-TMSI ::= SEQUENCE {
    mmec MMEC,
    m-TMSI BIT STRING (SIZE (32))
}

maxPageRec INTEGER ::= 16 --

END
